-- ==================================================================
-- Copyright (C) 2022 by  HUAWEI TECHNOLOGIES. All rights reserved.
-- 
-- Description: HUAWEI GTL MIB
-- Reference:
-- Version: V2.37
-- History:
-- <author>,  <date>,  <contents>
-- WangHaiwei   2007-1-16
-- ==================================================================
-- ==================================================================
-- 
-- Variables and types are imported
-- 
-- ==================================================================

    HUAWEI-GTL-MIB DEFINITIONS ::= BEGIN
 
        IMPORTS
            hwDatacomm            
                FROM HUAWEI-MIB   
            DisplayString 
                FROM SNMPv2-TC
            OBJECT-GROUP, MODULE-COMPLIANCE, NOTIFICATION-GROUP            
                FROM SNMPv2-CONF            
            Unsigned32, Integer32, OBJECT-TYPE, MODULE-IDENTITY, NOTIFICATION-TYPE            
                FROM SNMPv2-SMI;

        hwGtl MODULE-IDENTITY 
            LAST-UPDATED "202209291731Z"        -- Sep 29, 2022 at 17:31 GMT
            ORGANIZATION 
                "Huawei Technologies Co.,Ltd."
            CONTACT-INFO 
                "Huawei Industrial Base
                  Bantian, Longgang
                   Shenzhen 518129
                   People's Republic of China
                   Website: http://www.huawei.com
                   Email: support@huawei.com
                 "            
            DESCRIPTION 
                "The private mib file includes the general extent 
                information of the device.hwDatacomm(25).htGtl(142)"

            REVISION     "202209291731Z"
            DESCRIPTION  "V2.37, Add the hwGtlFeatureDefaultValue, hwGtlFeatureDefaultValueCleared"

            REVISION     "202207182145Z"
            DESCRIPTION  "V2.36, Add the hwGtlPosition"

            REVISION     "202207021040Z"
            DESCRIPTION  "V2.35, Modify the type of hwGtlRemainingDays"

            REVISION     "202206221030Z"
            DESCRIPTION  "V2.34, Change hwGtlFileDamaged, hwGtlFileDamagedResume to hwGtlDataDamaged, hwGtlDataDamagedResume"

            REVISION     "202206100930Z"
            DESCRIPTION  "V2.33, Add the hwGtlFileDamaged, hwGtlFileDamagedResume"

            REVISION     "202205141052Z"                                                                                    
            DESCRIPTION  "V2.32, Modify the content of hwGtlObjectGroup and hwGtlNotificationGroup"

            REVISION     "202204212047Z"                                                                                    
            DESCRIPTION  "V2.31, Add the hwGtlRemainingDays, hwGtlCloudServerOffline, hwGtlCloudServerOfflineCleared, hwGtlCloudServerOfflineLocked, hwGtlCloudServerOfflineLockedCleared"

            REVISION     "202107131214Z"                                                                                    
            DESCRIPTION  "V2.30, Add the hwGtlNextStartup"
            
            REVISION     "202102191441Z"                                                                                    
            DESCRIPTION  "V2.29, Add the hwGtlLicenseRevokeTicket, hwGtlMachineESN, hwGtlMachineESNChanged"

            REVISION     "202007171441Z"                                                                                    
            DESCRIPTION  "V2.28, Add the hwGtlCloudNearDeadline"

            REVISION     "202007031441Z"                                                                                    
            DESCRIPTION  "V2.27, Add the hwGtlItemExpire,hwGtlItemNearExpire"

            REVISION     "201907221000Z"                                                                                    
            DESCRIPTION  "V2.26, Modify the description of hwGtlItemTable"

            REVISION     "201907171700Z"                                                                                    
            DESCRIPTION  "V2.25, Add the hwGtlSnsExpire,hwGtlSnsNearExpire,hwGtlSnsEndDate"

            REVISION     "201810081700Z"                                                                                    
            DESCRIPTION  "V2.24, Add vb for hwGtlFeatureFunInactive,hwGtlFeatureFunInactiveCleared"

            REVISION     "201809151800Z"                                                                                    
            DESCRIPTION  "V2.23, Add the hwGtlLicenseStateChange,hwGtlLicensePreviousState,hwGtlLicenseState" 

            REVISION     "201805231136Z"                                                                                    
            DESCRIPTION  "V2.22, Add the hwGtlFeatureFunInactive,hwGtlFeatureFunInactiveCleared" 

            REVISION     "201803241606Z"                                                                                    
            DESCRIPTION  "V2.21, Add the hwGtlStackItemEntry"

            REVISION     "201801311626Z"                                                                                    
            DESCRIPTION  "V2.20, Add the hwGtlTrialResFeatureEnable,hwGtlTrialResFeatureDisable" 

            REVISION     "201801081643Z"                                                                                    
            DESCRIPTION  "V2.19,Restore deleted hwGtlItemIndex."

            REVISION     "201712191643Z"                                                                                    
            DESCRIPTION  "V2.18,Add hwGtlItemTrialRemainTime, hwGtlTrialFeatureNearExpire, hwGtlTrialFeatureNearExpireCleared, hwGtlTrialFeatureExpire, and hwGtlTrialFeatureExpireCleared."

            REVISION     "201711271643Z"                                                                                    
            DESCRIPTION  "V2.17, Modify para of alarm hwGtlResourceUsedUp, hwGtlResourceLack" 

            REVISION     "201710111643Z"                                                                                    
            DESCRIPTION  "V2.16, Modify description of hwGtlItemTable " 

            REVISION     "201708171643Z"                                                                                    
            DESCRIPTION  "V2.15, Modify description of hwGtlChassisID "  
                                
            REVISION     "201708141700Z"                                                                                    
            DESCRIPTION  "V2.14, Modify INDEX of hwGtlItemEntry, Delete hwGtlItemIndex, Add hwGtlItemState, hwGtlItemExpireDay "  

            REVISION     "201607271037Z"                                                                                    
            DESCRIPTION  "V2.13, Modify description of hwGtlFunctionInactive, hwGtlFunctionInactiveCleared, hwGtlResourceLack, hwGtlResourceLackCleared "  

            REVISION     "201606282020Z"                                                                                    
            DESCRIPTION  "V2.12, Add hwGtlAbnormal, hwGtlAbnormalCleared, hwGtlAbnormalReason "                     
                
            REVISION     "201605191118Z"                                                                                    
            DESCRIPTION  "V2.11, Add hwGtlFunctionInactive, hwGtlFunctionInactiveCleared, hwGtlResourceLack, hwGtlResourceLackCleared "                     
                
            REVISION     "201512311501Z"                                                                                    
            DESCRIPTION  "V2.10, Add hwGtlInitial, hwGtlInitialCleared, hwGtlBoardID  "     
               
            REVISION     "201508101714Z"                                                                                    
            DESCRIPTION  "V2.09, Add hwGtlItemInactive, hwGtlItemInactiveCleared  "     
 
            REVISION     "201507201148Z"                                                                                    
            DESCRIPTION  "V2.08, Add hwGtlEsnMismatchCleared" 
                
            REVISION     "201507141538Z"                                                                                    
            DESCRIPTION  "V2.07, Add hwGtlEsnMismatch" 

            REVISION     "201506041538Z"                                                                                    
            DESCRIPTION  "V2.06, Add hwGtlResourceOverload, hwGtlResourceOverloadCleared" 

            REVISION     "201412041538Z"                                                                                    
            DESCRIPTION  "V2.05, Add the hwGtlTrialFeatureNearDeadline, hwGtlTrialFeatureNearDeadlineCleared" 

            REVISION     "201403051428Z"                                                                                    
            DESCRIPTION  "V2.04, Add the hwGtlTrialFeatureEnable,hwGtlTrialFeatureDisable" 

            REVISION     "201308191042Z"                                                                                    
            DESCRIPTION  "V2.03, Add the hwGtlEmergencyStart,hwGtlEmergencyStop" 
            
            REVISION     "201308061134Z"                                                                                    
            DESCRIPTION  "V2.02, Add the hwGtlLicenseNotCommeral" 
            
            REVISION     "201307171614Z"                                                                                    
            DESCRIPTION  "V2.01, Add the hwGtlResourceUsedUpCleared  " 

            ::= { hwDatacomm 142 }
   
--
-- Node definitions
--
    
-- ==================================================================
-- 
-- ======================= definition begin =========================
-- 
-- ==================================================================  
        hwGtlMibObjects OBJECT IDENTIFIER ::= { hwGtl 1 }

        hwGtlDefaultValueReason OBJECT-TYPE
            SYNTAX OCTET STRING (SIZE (1..31))
            MAX-ACCESS accessible-for-notify
            STATUS current
            DESCRIPTION
                "The object specifies the reason why the system uses the default value."
            ::= { hwGtlMibObjects 1 }
        
        hwGtlResourceItem OBJECT-TYPE
            SYNTAX OCTET STRING (SIZE (1..31))
            MAX-ACCESS accessible-for-notify
            STATUS current
            DESCRIPTION
                "The object specifies the resource item which is nearly exhausted."
            ::= { hwGtlMibObjects 2 }

        hwGtlFeatureName OBJECT-TYPE
            SYNTAX OCTET STRING (SIZE (1..31))
            MAX-ACCESS accessible-for-notify
            STATUS current
            DESCRIPTION
                "The object specifies the feature name which is near deadline."
            ::= { hwGtlMibObjects 3 }

        hwGtlRemainTime OBJECT-TYPE
            SYNTAX Integer32
            MAX-ACCESS accessible-for-notify
            STATUS current
            DESCRIPTION
                "Remain time of the feature which is near deadline.The unit is day."
            ::= { hwGtlMibObjects 4 }

        hwGtlVerifyCode OBJECT-TYPE
            SYNTAX Integer32
            MAX-ACCESS accessible-for-notify
            STATUS current
            DESCRIPTION
                "The verify code returned when verify license file failed."
            ::= { hwGtlMibObjects 5 }

        hwGtlActive OBJECT-TYPE
            SYNTAX     OCTET STRING (SIZE (5..127))
            MAX-ACCESS read-write
            STATUS     current
            DESCRIPTION
                    "Active GTL license"
            ::= { hwGtlMibObjects 6 }
            
        hwGtlShowActLCSName OBJECT-TYPE
            SYNTAX     OCTET STRING (SIZE (5..127))
            MAX-ACCESS read-only
            STATUS     current
            DESCRIPTION
                    "Show active GTL license file name"
            ::= { hwGtlMibObjects 7 }    

        hwGtlItemTable OBJECT-TYPE
            SYNTAX SEQUENCE OF HwGtlItemEntry
            MAX-ACCESS not-accessible
            STATUS current
            DESCRIPTION
                "This table describes license control item information, helping you query the name, activation value, use value, description, activation status, and expiration date information about license control items. In a multi-chassis or stack system, performing the SNMP walk operation on the table obtains information about the license control items on the first board. This board may not be the master main control board."
            ::= { hwGtlMibObjects 8 }
            
        hwGtlItemEntry OBJECT-TYPE
            SYNTAX HwGtlItemEntry
            MAX-ACCESS not-accessible
            STATUS current
            DESCRIPTION
                "A GTL license item information entry. Each entry consists of information of a item."
            INDEX { hwGtlItemIndex}
            ::= { hwGtlItemTable 1 }
            
        HwGtlItemEntry ::=
            SEQUENCE { 
                hwGtlItemIndex
                    Unsigned32,
                hwGtlItemName
                    DisplayString,
                hwGtlItemControlValue
                    Unsigned32,
                hwGtlItemUsedValue
                    Unsigned32,
                hwGtlItemDescription
                    DisplayString,
                hwGtlItemState
                    DisplayString,
                hwGtlItemExpireDay
                    DisplayString,
                hwGtlItemTrialRemainTime
                    Unsigned32,
                hwGtlItemTrialResRemainTime
                    Unsigned32
             }

        hwGtlItemIndex OBJECT-TYPE
            SYNTAX Unsigned32
            MAX-ACCESS not-accessible
            STATUS current
            DESCRIPTION
                "The index of the GTL license item."
            ::= { hwGtlItemEntry 1 }

        hwGtlItemName OBJECT-TYPE
            SYNTAX     DisplayString
            MAX-ACCESS read-only
            STATUS     current
            DESCRIPTION
                "This object indicates the name of a license control item."
            ::= { hwGtlItemEntry 2 }  

        hwGtlItemControlValue OBJECT-TYPE
            SYNTAX Unsigned32
            MAX-ACCESS read-only
            STATUS current
            DESCRIPTION
                "The value of this object identifies the activation value of a license control item."
            ::= { hwGtlItemEntry 3 }

        hwGtlItemUsedValue OBJECT-TYPE
            SYNTAX Unsigned32
            MAX-ACCESS read-only
            STATUS current
            DESCRIPTION
                "The value of this object identifies the use value of a license control item."
            ::= { hwGtlItemEntry 4 }

        hwGtlItemDescription OBJECT-TYPE
            SYNTAX     DisplayString
            MAX-ACCESS read-only
            STATUS     current
            DESCRIPTION
                "This object indicates the description of a license control item."
            ::= { hwGtlItemEntry 5 }  
            
        hwGtlItemState OBJECT-TYPE
            SYNTAX     DisplayString
            MAX-ACCESS read-only
            STATUS     current
            DESCRIPTION
                "The value of this object identifies the activation status of a license control item."
            ::= { hwGtlItemEntry 6 }  

        hwGtlItemExpireDay OBJECT-TYPE
            SYNTAX     DisplayString
            MAX-ACCESS read-only
            STATUS     current
            DESCRIPTION
                "This object indicates the expiration date of a license control item."
            ::= { hwGtlItemEntry 7 } 

        hwGtlItemTrialRemainTime OBJECT-TYPE
            SYNTAX     Unsigned32
            MAX-ACCESS read-only
            STATUS     current
            DESCRIPTION
                "This object indicates the remaining trial days of a license control item."
            ::= { hwGtlItemEntry 8 }

        hwGtlItemTrialResRemainTime OBJECT-TYPE
            SYNTAX     Unsigned32
            MAX-ACCESS read-only
            STATUS     current
            DESCRIPTION
                "This object indicates the remaining trial days of resource license control item."
            ::= { hwGtlItemEntry 9 }

        hwGtlChassisID OBJECT-TYPE
        SYNTAX     OCTET STRING (SIZE (1..32))
        MAX-ACCESS accessible-for-notify
        STATUS     current
        DESCRIPTION
            "Description of the alarm chassis whose license control items are inconsistent with those of the main chassis."
        ::= { hwGtlMibObjects 9 }

        hwGtlBoardID OBJECT-TYPE
        SYNTAX     OCTET STRING (SIZE (1..32))
        MAX-ACCESS accessible-for-notify
        STATUS     current
        DESCRIPTION
            "Show board description."
        ::= { hwGtlMibObjects 10 }

        hwGtlAbnormalReason OBJECT-TYPE
        SYNTAX INTEGER
            {
            startLibrary(10),
            requestRespond(11),
            processMessage(12),
            sendRequest(13),
            processRequest(14),
            licenseAbnormal(15)
            }
        MAX-ACCESS accessible-for-notify
        STATUS     current
        DESCRIPTION
            "Show abnormal reason of license:
            startLibrary(10): Failed to start the license library
            requestRespond(11): The backup request was not responded
            processMessage(12): Failed to process the backup message
            sendRequest(13): Failed to send a backup request
            processRequest(14): Failed to process the backup request
            licenseAbnormal(15): The license may be abnormal
            "
        ::= { hwGtlMibObjects 11 }

        hwGtlStackItemTable OBJECT-TYPE
            SYNTAX SEQUENCE OF HwGtlStackItemEntry
            MAX-ACCESS not-accessible
            STATUS current
            DESCRIPTION
                "This table describes license control item information only under stack or cluster device, helping you query the name, activation value, use value, description, activation status, and expiration date information about license control items."
            ::= { hwGtlMibObjects 12 }
            
        hwGtlStackItemEntry OBJECT-TYPE
            SYNTAX HwGtlStackItemEntry
            MAX-ACCESS not-accessible
            STATUS current
            DESCRIPTION
                "A GTL license item information entry. Each entry consists of information of a item."
            INDEX { hwGtlStackChassisId, hwGtlStackBoardId, hwGtlStackItemIndex}
            ::= { hwGtlStackItemTable 1 }
            
        HwGtlStackItemEntry ::=
            SEQUENCE { 
                hwGtlStackChassisId
                    Unsigned32,
                hwGtlStackBoardId
                    Unsigned32,
                hwGtlStackItemIndex
                    Unsigned32,
                hwGtlStackItemName
                    DisplayString,
                hwGtlStackItemControlValue
                    Unsigned32,
                hwGtlStackItemUsedValue
                    Unsigned32,
                hwGtlStackItemDescription
                    DisplayString,
                hwGtlStackItemState
                    DisplayString,
                hwGtlStackItemExpireDay
                    DisplayString
             }

        hwGtlStackChassisId OBJECT-TYPE
            SYNTAX Unsigned32
            MAX-ACCESS not-accessible
            STATUS current
            DESCRIPTION
                "The chassis id of the GTL license item."
            ::= { hwGtlStackItemEntry 1 }

        hwGtlStackBoardId OBJECT-TYPE
            SYNTAX     Unsigned32
            MAX-ACCESS not-accessible
            STATUS     current
            DESCRIPTION
                "The board id of the GTL license item."
            ::= { hwGtlStackItemEntry 2 }  

        hwGtlStackItemIndex OBJECT-TYPE
            SYNTAX Unsigned32
            MAX-ACCESS not-accessible
            STATUS current
            DESCRIPTION
                "The index of the GTL license item."
            ::= { hwGtlStackItemEntry 3 }

        hwGtlStackItemName OBJECT-TYPE
            SYNTAX     DisplayString
            MAX-ACCESS read-only
            STATUS     current
            DESCRIPTION
                "This object indicates the name of a license control item."
            ::= { hwGtlStackItemEntry 4 }  

        hwGtlStackItemControlValue OBJECT-TYPE
            SYNTAX Unsigned32
            MAX-ACCESS read-only
            STATUS current
            DESCRIPTION
                "The value of this object identifies the activation value of a license control item."
            ::= { hwGtlStackItemEntry 5 }

        hwGtlStackItemUsedValue OBJECT-TYPE
            SYNTAX Unsigned32
            MAX-ACCESS read-only
            STATUS current
            DESCRIPTION
                "The value of this object identifies the use value of a license control item."
            ::= { hwGtlStackItemEntry 6 }

        hwGtlStackItemDescription OBJECT-TYPE
            SYNTAX     DisplayString
            MAX-ACCESS read-only
            STATUS     current
            DESCRIPTION
                "This object indicates the description of a license control item."
            ::= { hwGtlStackItemEntry 7 }  
            
        hwGtlStackItemState OBJECT-TYPE
            SYNTAX     DisplayString
            MAX-ACCESS read-only
            STATUS     current
            DESCRIPTION
                "The value of this object identifies the activation status of a license control item."
            ::= { hwGtlStackItemEntry 8 }  

        hwGtlStackItemExpireDay OBJECT-TYPE
            SYNTAX     DisplayString
            MAX-ACCESS read-only
            STATUS     current
            DESCRIPTION
                "This object indicates the expiration date of a license control item."
            ::= { hwGtlStackItemEntry 9 } 

        hwGtlLicensePreviousState OBJECT-TYPE
        SYNTAX     OCTET STRING (SIZE (1..16))
        MAX-ACCESS accessible-for-notify
        STATUS     current
        DESCRIPTION
            "License previous state."
        ::= { hwGtlMibObjects 13 }

        hwGtlLicenseState OBJECT-TYPE
        SYNTAX     OCTET STRING (SIZE (1..16))
        MAX-ACCESS accessible-for-notify
        STATUS     current
        DESCRIPTION
            "License current state."
        ::= { hwGtlMibObjects 14 }

        hwGtlSnsEndDate OBJECT-TYPE
        SYNTAX     OCTET STRING (SIZE (1..16))
        MAX-ACCESS accessible-for-notify
        STATUS     current
        DESCRIPTION
            "License SnS end date."
        ::= { hwGtlMibObjects 15 }

        hwGtlLicenseRevokeTicket OBJECT-TYPE
        SYNTAX     OCTET STRING (SIZE (1..136))
        MAX-ACCESS accessible-for-notify
        STATUS     current
        DESCRIPTION
            "License revoke ticket."
        ::= { hwGtlMibObjects 16 }

        hwGtlMachineESN OBJECT-TYPE
        SYNTAX     OCTET STRING (SIZE (1..2056))
        MAX-ACCESS accessible-for-notify
        STATUS     current
        DESCRIPTION
            "License revoke ticket."
        ::= { hwGtlMibObjects 17 }

        hwGtlNextStartup OBJECT-TYPE
            SYNTAX     OCTET STRING (SIZE (5..127))
            MAX-ACCESS read-write
            STATUS     current
            DESCRIPTION
                "The license file for the next startup."
            ::= { hwGtlMibObjects 18 }

        hwGtlRemainingDays OBJECT-TYPE
            SYNTAX     Unsigned32 (1..60)
            MAX-ACCESS accessible-for-notify
            STATUS     current
            DESCRIPTION
                "Remaining days of device offline locking."
            ::= { hwGtlMibObjects 19 }

        hwGtlPosition OBJECT-TYPE
            SYNTAX     OCTET STRING (SIZE (1..32))
            MAX-ACCESS accessible-for-notify
            STATUS     current
            DESCRIPTION
                "Description of the alarm location."
            ::= { hwGtlMibObjects 20 }

        hwGtlNotifications OBJECT IDENTIFIER ::= { hwGtl 2 }

        hwGtlDefaultValue NOTIFICATION-TYPE
            OBJECTS { hwGtlDefaultValueReason, hwGtlChassisID }
            STATUS current
            DESCRIPTION 
                "Notification represents that the system will use default value if the license file fails to pass the verification."
            ::= { hwGtlNotifications 1 }

        hwGtlResourceUsedUp NOTIFICATION-TYPE
            OBJECTS { hwGtlResourceItem, hwGtlItemDescription }
            STATUS current
            DESCRIPTION 
                "Notification represents the resource is nearly exhausted."
            ::= { hwGtlNotifications 2 }

        hwGtlNearDeadline NOTIFICATION-TYPE
            OBJECTS { hwGtlFeatureName, hwGtlRemainTime, hwGtlChassisID }
            STATUS current
            DESCRIPTION 
                "Notification represents the feature is near deadline."
            ::= { hwGtlNotifications 3 }

        hwGtlLicenseVerifyFailed NOTIFICATION-TYPE
            OBJECTS { hwGtlVerifyCode }
            STATUS current
            DESCRIPTION 
                "Notification represents license verification failed.
                The reason why license verification failed can be:
                1 represents that the ESN or version of the device and the license file mismatch.
                2 represents that the license file has expired.
                3 represents that the product type of the device and the license file mismatch.
                4 represents that the license file is invalid."
            ::= { hwGtlNotifications 4 }
        
        hwGtlExpired NOTIFICATION-TYPE
            STATUS current
            DESCRIPTION 
                "Notification represents the license has expired."
            ::= { hwGtlNotifications 5 }

        hwGtlItemMismatch NOTIFICATION-TYPE
            OBJECTS { hwGtlChassisID }
            STATUS current
            DESCRIPTION 
                "License item mismatch with the main chassis."
            ::= { hwGtlNotifications 6 }

        hwGtlDefaultValueCleared NOTIFICATION-TYPE
            OBJECTS { hwGtlDefaultValueReason, hwGtlChassisID }
            STATUS current
            DESCRIPTION 
                "The notification represents that the system will use default value if the license file fails to pass the verification is cleared."
            ::= { hwGtlNotifications 7 }

        hwGtlNearDeadlineCleared NOTIFICATION-TYPE
            OBJECTS { hwGtlFeatureName, hwGtlRemainTime, hwGtlChassisID }
            STATUS current
            DESCRIPTION 
                "The notification represents the feature is near deadline is cleared."
            ::= { hwGtlNotifications 8 }

        hwGtlItemMismatchCleared NOTIFICATION-TYPE
            OBJECTS { hwGtlChassisID }
            STATUS current
            DESCRIPTION 
                "The notification represents the license item mismatch with the main chassis is cleared."
            ::= { hwGtlNotifications 9 }

        hwGtlResourceUsedUpCleared NOTIFICATION-TYPE
            OBJECTS { hwGtlResourceItem, hwGtlItemDescription }
            STATUS current
            DESCRIPTION 
                "The notification represents the resource is nearly exhausted is cleared."
            ::= { hwGtlNotifications 10 }

        hwGtlLicenseNotCommeral NOTIFICATION-TYPE        
        STATUS current
        DESCRIPTION 
                "The notification represents the license is not commerial."
        ::= { hwGtlNotifications 11}
          
        hwGtlEmergencyStart NOTIFICATION-TYPE
            STATUS current
            DESCRIPTION 
                "Notification represents the license emergency is started."
            ::= { hwGtlNotifications 12 }
            
        hwGtlEmergencyStop NOTIFICATION-TYPE
            STATUS current
            DESCRIPTION 
                "Notification represents the license mergency is stopped after 7 days."
            ::= { hwGtlNotifications 13 } 

        hwGtlTrialFeatureEnable NOTIFICATION-TYPE
            OBJECTS { hwGtlFeatureName, hwGtlRemainTime}
            STATUS current
            DESCRIPTION 
                "Notification represents the trial feature is enable."
            ::= { hwGtlNotifications 14 } 

        hwGtlTrialFeatureDisable NOTIFICATION-TYPE
            OBJECTS { hwGtlFeatureName}
            STATUS current
            DESCRIPTION 
                "Notification represents the trial feature is disable ."
            ::= { hwGtlNotifications 15} 

       hwGtlTrialFeatureNearDeadline NOTIFICATION-TYPE
            OBJECTS { hwGtlFeatureName, hwGtlRemainTime, hwGtlChassisID }
            STATUS current
            DESCRIPTION 
                "The trial feature is about to expire."
            ::= { hwGtlNotifications 16 }           

       hwGtlTrialFeatureNearDeadlineCleared NOTIFICATION-TYPE
            OBJECTS { hwGtlFeatureName, hwGtlRemainTime, hwGtlChassisID }
            STATUS current
            DESCRIPTION 
                "The alarm indicating that the trial feature is about to expire is cleared."
            ::= { hwGtlNotifications 17 }  

        hwGtlResourceOverload NOTIFICATION-TYPE
            OBJECTS { hwGtlResourceItem }
            STATUS current
            DESCRIPTION 
                "Notification represents the resource has been used up."
            ::= { hwGtlNotifications 18 }

       hwGtlResourceOverloadCleared NOTIFICATION-TYPE
            OBJECTS { hwGtlResourceItem }
            STATUS current
            DESCRIPTION 
                "The notification represents the resource has been used up is cleared."
            ::= { hwGtlNotifications 19 }
            
       hwGtlEsnMismatch NOTIFICATION-TYPE
            OBJECTS { hwGtlChassisID }
            STATUS current
            DESCRIPTION 
                "The notification represents the mismatch between the device ESN and license file."
            ::= { hwGtlNotifications 20 }

       hwGtlEsnMismatchCleared NOTIFICATION-TYPE
            OBJECTS { hwGtlChassisID }
            STATUS current
            DESCRIPTION 
                "The notification represents the mismatch between the device ESN and license file is cleared."
            ::= { hwGtlNotifications 21 }
            
        hwGtlItemInactive NOTIFICATION-TYPE
            OBJECTS { hwGtlResourceItem }
            STATUS current
            DESCRIPTION 
                "Notification represents the item is inactive."
            ::= { hwGtlNotifications 22 }
            
        hwGtlItemInactiveCleared NOTIFICATION-TYPE
            OBJECTS { hwGtlResourceItem }
            STATUS current
            DESCRIPTION 
                "The notification represents the item is inactive is cleared."
            ::= { hwGtlNotifications 23 }

        hwGtlInitial NOTIFICATION-TYPE
            OBJECTS { hwGtlChassisID, hwGtlBoardID }
            STATUS current
            DESCRIPTION 
                "Notification represents current license had been initialized."
            ::= { hwGtlNotifications 24 }
            
        hwGtlInitialCleared NOTIFICATION-TYPE
            OBJECTS { hwGtlChassisID, hwGtlBoardID }
            STATUS current
            DESCRIPTION 
                "The notification represents current license had been initialized is cleared."
            ::= { hwGtlNotifications 25 }
            
            
        hwGtlFunctionInactive NOTIFICATION-TYPE
            OBJECTS { hwGtlItemName }
            STATUS current
            DESCRIPTION 
                "The alarm indicates that the control item is not activated."
            ::= { hwGtlNotifications 26 }
            
        hwGtlFunctionInactiveCleared NOTIFICATION-TYPE
            OBJECTS { hwGtlItemName }
            STATUS current
            DESCRIPTION 
                "The alarm indicating that the control item is not activated is cleared."
            ::= { hwGtlNotifications 27 }

        hwGtlResourceLack NOTIFICATION-TYPE
            OBJECTS { hwGtlItemName, hwGtlItemControlValue, hwGtlItemUsedValue, hwGtlItemDescription }
            STATUS current
            DESCRIPTION 
                "The alarm indicates that the current resources are insufficient."
            ::= { hwGtlNotifications 28 }
            
        hwGtlResourceLackCleared NOTIFICATION-TYPE
            OBJECTS { hwGtlItemName, hwGtlItemControlValue, hwGtlItemUsedValue, hwGtlItemDescription }
            STATUS current
            DESCRIPTION 
                "The alarm indicating that the current resources are insufficient is cleared."
            ::= { hwGtlNotifications 29 }           

        hwGtlAbnormal NOTIFICATION-TYPE
            OBJECTS { hwGtlChassisID, hwGtlBoardID, hwGtlAbnormalReason }
            STATUS current
            DESCRIPTION 
                "Notification represents license function is abnormal."
            ::= { hwGtlNotifications 30 }
            
        hwGtlAbnormalCleared NOTIFICATION-TYPE
            OBJECTS { hwGtlChassisID, hwGtlBoardID, hwGtlAbnormalReason }
            STATUS current
            DESCRIPTION 
                "Notification represents license function is abnormal is cleared."
            ::= { hwGtlNotifications 31 } 

        hwGtlTrialFeatureNearExpire NOTIFICATION-TYPE
            OBJECTS { hwGtlItemName, hwGtlItemDescription, hwGtlItemTrialRemainTime }
            STATUS current
            DESCRIPTION 
                "The notification indicates that the trial of the license control item is about to expire."
            ::= { hwGtlNotifications 32 }

        hwGtlTrialFeatureNearExpireCleared NOTIFICATION-TYPE
            OBJECTS { hwGtlItemName, hwGtlItemDescription, hwGtlItemTrialRemainTime }
            STATUS current
            DESCRIPTION 
                "The notification indicates that the notification indicating that the trial of the license control item is about to expire is cleared."
            ::= { hwGtlNotifications 33 }

        hwGtlTrialFeatureExpire NOTIFICATION-TYPE
            OBJECTS { hwGtlItemName, hwGtlItemDescription }
            STATUS current
            DESCRIPTION 
                "The notification indicates that the trial of the license control item has expired."
            ::= { hwGtlNotifications 34 }

        hwGtlTrialFeatureExpireCleared NOTIFICATION-TYPE
            OBJECTS { hwGtlItemName, hwGtlItemDescription }
            STATUS current
            DESCRIPTION 
                "The notification indicates that the notification indicating that the trial of the license control item has expired is cleared."
            ::= { hwGtlNotifications 35 }

        hwGtlTrialResFeatureEnable NOTIFICATION-TYPE
            OBJECTS { hwGtlItemTrialResRemainTime}
            STATUS current
            DESCRIPTION 
                "Notification represents the trial of resource item is enable."
            ::= { hwGtlNotifications 36 } 

        hwGtlTrialResFeatureDisable NOTIFICATION-TYPE
            STATUS current
            DESCRIPTION 
                "Notification represents the trial of resource item is disable ."
            ::= { hwGtlNotifications 37}           
        
        hwGtlFeatureFunInactive NOTIFICATION-TYPE
            OBJECTS { hwGtlItemName, hwGtlFeatureName }
            STATUS current
            DESCRIPTION 
                "The alarm indicates that the control item is not activated."
            ::= { hwGtlNotifications 38}

        hwGtlFeatureFunInactiveCleared NOTIFICATION-TYPE
            OBJECTS { hwGtlItemName, hwGtlFeatureName }
            STATUS current
            DESCRIPTION 
                "The alarm indicating that the control item is not activated is cleared."
            ::= { hwGtlNotifications 39}

        hwGtlLicenseStateChange NOTIFICATION-TYPE
            OBJECTS { hwGtlLicensePreviousState,hwGtlLicenseState}
            STATUS current
            DESCRIPTION 
                "The alarm indicating that the license status has changed."
            ::= { hwGtlNotifications 40}

        hwGtlSnsNearExpire NOTIFICATION-TYPE
            OBJECTS { hwGtlSnsEndDate, hwGtlChassisID }
            STATUS current
            DESCRIPTION 
                "The alarm indicates that the SnS is near deadline."
            ::= { hwGtlNotifications 41}

        hwGtlSnsNearExpireCleared NOTIFICATION-TYPE
            OBJECTS { hwGtlSnsEndDate, hwGtlChassisID }
            STATUS current
            DESCRIPTION 
                "The alarm indicating that the SnS is near deadline is cleared."
            ::= { hwGtlNotifications 42}

        hwGtlSnsExpire NOTIFICATION-TYPE
            OBJECTS { hwGtlChassisID }
            STATUS current
            DESCRIPTION 
                "The alarm indicates that the SnS is near deadline."
            ::= { hwGtlNotifications 43}

        hwGtlSnsExpireCleared NOTIFICATION-TYPE
            OBJECTS { hwGtlChassisID }
            STATUS current
            DESCRIPTION 
                "The alarm indicating that the SnS is near deadline is cleared."
            ::= { hwGtlNotifications 44}

        hwGtlItemNearExpire NOTIFICATION-TYPE
            OBJECTS { hwGtlChassisID }
            STATUS current
            DESCRIPTION 
                "The alarm indicates that the SnS of the cloud-based license sales item has expired."
            ::= { hwGtlNotifications 45}

        hwGtlItemNearExpireResume NOTIFICATION-TYPE
            OBJECTS { hwGtlChassisID }
            STATUS current
            DESCRIPTION 
                "The alarm indicating that the SnS of the cloud-based license sales item has expired is cleared."
            ::= { hwGtlNotifications 46}

        hwGtlItemExpire NOTIFICATION-TYPE
            OBJECTS { hwGtlChassisID }
            STATUS current
            DESCRIPTION 
                "The alarm indicates that the SnS of the cloud-based license sales item expires."
            ::= { hwGtlNotifications 47}

        hwGtlItemExpireResume NOTIFICATION-TYPE
            OBJECTS { hwGtlChassisID }
            STATUS current
            DESCRIPTION 
                "The alarm indicating that the SnS of the cloud-based license sales item expires is cleared."
            ::= { hwGtlNotifications 48}

        hwGtlCloudNearDeadline NOTIFICATION-TYPE
            OBJECTS { hwGtlRemainTime }
            STATUS current
            DESCRIPTION 
                "Notification represents the cloud license is near deadline."
            ::= { hwGtlNotifications 49}

        hwGtlCloudNearDeadlineCleared NOTIFICATION-TYPE
            OBJECTS { hwGtlRemainTime }
            STATUS current
            DESCRIPTION 
                "The alarm indicating that the cloud license is near deadline is cleared."
            ::= { hwGtlNotifications 50}

        hwGtlMachineESNChanged NOTIFICATION-TYPE
            OBJECTS { hwGtlLicenseRevokeTicket, hwGtlMachineESN }
            STATUS current
            DESCRIPTION 
                "The alarm indicating the license is revoked because the ESN is changed."
            ::= { hwGtlNotifications 51}

        hwGtlCloudServerOffline NOTIFICATION-TYPE
            OBJECTS { hwGtlRemainingDays }
            STATUS current
            DESCRIPTION
                "The alarm indicating that the device is disconnected from the cloud license server."
            ::= { hwGtlNotifications 52}
        hwGtlCloudServerOfflineCleared NOTIFICATION-TYPE
            STATUS current
            DESCRIPTION
                "The alarm indicating disconnection between the device and the cloud license server is cleared."
            ::= { hwGtlNotifications 53}
        hwGtlCloudServerOfflineLocked NOTIFICATION-TYPE
            STATUS current
            DESCRIPTION
                "The device is locked because the device is disconnected from the cloud license server."
            ::= { hwGtlNotifications 54}
        hwGtlCloudServerOfflineLockedCleared NOTIFICATION-TYPE
            STATUS current
            DESCRIPTION
                "The alarm indicating that the device is locked due to disconnection between the device and the cloud license server is cleared."
            ::= { hwGtlNotifications 55}

        hwGtlDataDamaged NOTIFICATION-TYPE
            OBJECTS { hwGtlPosition }
            STATUS current
            DESCRIPTION
                "This notification indicates that the current license data is damaged."
            ::= { hwGtlNotifications 56}

        hwGtlDataDamagedResume NOTIFICATION-TYPE
            OBJECTS { hwGtlPosition }
            STATUS current
            DESCRIPTION
                "This notification indicates that the license data damage alarm has been cleared."
            ::= { hwGtlNotifications 57}

        hwGtlFeatureDefaultValue NOTIFICATION-TYPE
            OBJECTS { hwGtlFeatureName, hwGtlPosition, hwGtlDefaultValueReason }
            STATUS current
            DESCRIPTION 
                "Notification represents the feature uses the default value."
            ::= { hwGtlNotifications 58 }

        hwGtlFeatureDefaultValueCleared NOTIFICATION-TYPE
            OBJECTS { hwGtlFeatureName, hwGtlPosition, hwGtlDefaultValueReason }
            STATUS current
            DESCRIPTION 
                "Notification represents the feature uses the default value is cleared."
            ::= { hwGtlNotifications 59 }

--    Conformance information            
        hwGtlConformance OBJECT IDENTIFIER ::= { hwGtl 3 }

        hwGtlCompliances OBJECT IDENTIFIER ::= { hwGtlConformance 1 }

        hwGtlCompliance MODULE-COMPLIANCE
            STATUS current
            DESCRIPTION 
                "The compliance statement for systems supporting 
                the HUAWEI-GTL-MIB."
            MODULE -- this module
                MANDATORY-GROUPS { hwGtlObjectGroup, hwGtlNotificationGroup }
            ::= { hwGtlCompliances 1 }

        hwGtlGroups OBJECT IDENTIFIER ::= { hwGtlConformance 2 }

        hwGtlObjectGroup OBJECT-GROUP
            OBJECTS { hwGtlDefaultValueReason, hwGtlResourceItem, hwGtlFeatureName, hwGtlRemainTime, hwGtlVerifyCode, 
                      hwGtlActive, hwGtlShowActLCSName, hwGtlItemName, hwGtlItemControlValue, hwGtlItemUsedValue, hwGtlItemDescription, hwGtlItemState, hwGtlItemExpireDay, hwGtlItemTrialRemainTime, hwGtlItemTrialResRemainTime, hwGtlChassisID, hwGtlBoardID, hwGtlAbnormalReason, hwGtlStackItemName, hwGtlStackItemControlValue, hwGtlStackItemUsedValue, hwGtlStackItemDescription, hwGtlStackItemState, hwGtlStackItemExpireDay, hwGtlLicensePreviousState, hwGtlLicenseState, hwGtlSnsEndDate, hwGtlLicenseRevokeTicket, hwGtlMachineESN, hwGtlNextStartup, hwGtlRemainingDays, hwGtlPosition}
            STATUS current
            DESCRIPTION 
                "The GTL attribute group."
            ::= { hwGtlGroups 1 }

        hwGtlNotificationGroup NOTIFICATION-GROUP
            NOTIFICATIONS { hwGtlDefaultValue, hwGtlResourceUsedUp, hwGtlNearDeadline, hwGtlLicenseVerifyFailed, hwGtlExpired, hwGtlItemMismatch, hwGtlDefaultValueCleared, hwGtlNearDeadlineCleared, hwGtlItemMismatchCleared, hwGtlResourceUsedUpCleared, hwGtlLicenseNotCommeral, hwGtlEmergencyStart, hwGtlEmergencyStop, hwGtlTrialFeatureEnable, hwGtlTrialFeatureDisable, hwGtlTrialFeatureNearDeadline, hwGtlTrialFeatureNearDeadlineCleared, hwGtlResourceOverload, hwGtlResourceOverloadCleared, hwGtlEsnMismatch, hwGtlEsnMismatchCleared, hwGtlItemInactive, 
            hwGtlItemInactiveCleared, hwGtlInitial, hwGtlInitialCleared, hwGtlFunctionInactive, hwGtlFunctionInactiveCleared, hwGtlResourceLack, hwGtlResourceLackCleared, hwGtlAbnormal, 
            hwGtlAbnormalCleared,  hwGtlTrialResFeatureEnable, hwGtlTrialResFeatureDisable, hwGtlFeatureFunInactive, hwGtlFeatureFunInactiveCleared, hwGtlLicenseStateChange,
            hwGtlSnsNearExpire,hwGtlSnsNearExpireCleared,hwGtlSnsExpire,hwGtlSnsExpireCleared,hwGtlItemNearExpire,hwGtlItemNearExpireResume,hwGtlItemExpire,hwGtlItemExpireResume, 
            hwGtlCloudNearDeadline, hwGtlCloudNearDeadlineCleared, hwGtlMachineESNChanged, hwGtlCloudServerOffline, hwGtlCloudServerOfflineCleared, hwGtlCloudServerOfflineLocked, 
            hwGtlCloudServerOfflineLockedCleared, hwGtlDataDamaged, hwGtlDataDamagedResume, hwGtlFeatureDefaultValue, hwGtlFeatureDefaultValueCleared }
            STATUS current
            DESCRIPTION 
                "The notification group."
            ::= { hwGtlGroups 2 }
    
    END
